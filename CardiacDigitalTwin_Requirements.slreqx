# CardiacDigitalTwin_Requirements

## REQ_CDT_001: When the prescribed beta-blocker dose (beta_blocker_dose_mg) increases from 50 mg to 60 mg, the cardiac digital twin shall reduce the steady-state heart rate by at least 0.5 bpm. (Functional)
System-level dose-response acceptance criterion for the metoprolol +20% titration scenario.
The chronotropic stage uses a Hill/Emax receptor-binding model (emax_bpm=18, ec50_mg=35, hill_n=1.5),
so the drug effect saturates: because the curve is already past its EC50 at 50 mg, the marginal effect
of a further 20% dose increase is small (closed-loop HR drop about 0.85 bpm; open-loop about 1.1 bpm).
The 0.5 bpm threshold reflects this saturating reality rather than a linear extrapolation.
Steady state is the response after t >= 5 * pk_time_constant (1800 s).
Verified by validation/beta_blocker_dose_response.feature (Simulink Test, open-loop Hill scenarios).
Trace target: top-level pipeline BetaBlockerDose -> BetaBlockerPK -> HeartRateModel.
- Rationale: Demonstrates the digital twin produces a clinically directionally-correct chronotropic response to dose escalation, enabling its use as a decision-support tool for cardiologist titration review. The modest threshold captures Hill-curve saturation near Emax and the partial heart-rate restoration provided by the baroreflex loop.
- Keywords: draft, auto-generated, system, dose-response

### REQ_CDT_002: At steady state, the cardiac digital twin shall compute the drug-induced heart-rate reduction as a Hill/Emax function of plasma concentration C: emax_bpm (18 bpm) * C^hill_n / (ec50_mg^hill_n + C^hill_n), with hill_n=1.5 and ec50_mg=35 mg, within +/- 0.5 bpm tolerance, for any dose in the range [0 mg, 145 mg]. (Functional)
Performance requirement on the HeartRateModel subsystem chronotropic response.
HR_drug = baseline_heart_rate - emax_bpm * C^hill_n / (ec50_mg^hill_n + C^hill_n).
The Hill form captures receptor-binding saturation, so the marginal effect of dose escalation
shrinks as dose rises - the central behaviour the demo demonstrates.
Tolerance +/- 0.5 bpm covers first-order PK settling (about 5*tau = 9000 s to within 0.7%) and
small numerical drift, while still detecting a real calibration error.
Validity ceiling [0,145] mg: the HR saturation clamp (floor 40 bpm) marks the edge of the model's
validity domain. The Hill drug effect alone removes at most emax_bpm (~18 bpm), so the clamp never
engages at therapeutic doses; the bound documents where the model is no longer claimed representative.
- Rationale: Pins the model's chronotropic response to a calibrated, clinically plausible saturating curve. Receptor-binding saturation is precisely why a +20% dose step produces only a small marginal heart-rate change.
- Keywords: draft, auto-generated, performance, hill-emax

### REQ_CDT_003: If the prescribed dose lies within the therapeutic range [0 mg, 100 mg], then the cardiac digital twin shall maintain steady-state cardiac output at or above 4.0 L/min. (Functional)
Safety floor on the CardiacOutputModel output (CO = HR * stroke_volume_mL / 1000).
4.0 L/min corresponds to a cardiac index of about 2.0 L/min/m^2 for a typical adult (BSA ~2.0 m^2),
the conventional lower bound of adequate resting perfusion.
The requirement holds across the entire therapeutic range, and the Hill saturation is what makes that
true: because the drug effect plateaus near emax_bpm, heart rate never collapses the way a constant-gain
model would. At 100 mg the open-loop steady state is HR ~60.1 bpm and CO ~4.21 L/min - above the 4.0
floor even with the baroreflex switched off; the closed-loop value is higher still (~4.6 L/min) because
the reflex restores part of the heart-rate drop. The safety margin falls out of the pharmacodynamics
rather than being asserted as a bare guard.
Verification is traced so the margin is checked on every run rather than assumed.
- Rationale: Flags any dosing recommendation that would push the simulated patient below the clinical perfusion threshold. Receptor saturation in the Hill model supplies the margin that keeps cardiac output above 4.0 L/min across the therapeutic dose range.
- Keywords: draft, auto-generated, safety, cardiac-output
